FME workspace 1-Chargement_OSM_mapzen2postgis.fmw

Parameters:
- SourceDataset_SHAPE = https://s3.amazonaws.com/metro-extracts.mapzen.com/grand-avignon.osm2pgsql-shapefiles.zip   # Fichier(s) Esri Shape source 
- DestDataset_POSTGIS_3 = osm   # Jeu de données destination PostGIS 

Readers:
- SHAPE_1: SHAPE from $(SourceDataset_SHAPE) in EPSG:4326

Writers:
- POSTGIS_1: POSTGIS to $(DestDataset_POSTGIS_3) in EPSG:2154

Note: Script d'intégration des données OSM / Les données sont extraites du site http://mapzen.com/ / Au préalable si n'existe pas il faut avoir créer la ville / Les données sont générées toutes les semaines / Le script FME télécharge automatiquement la Zone du GA en OSM2PGSQL SHP (saisie de l'url dans le chemin d'accès des données sources) pour le charger la base en postgres en le reprojetant en 2154 / url grand avignon : https://s3.amazonaws.com/metro-extracts.mapzen.com/grand-avignon.osm2pgsql-shapefiles.zip / Durée d'execution du script 4'20"

Bookmark: Intégration données OSM Planet
Note: grand-avignon.osm-polygon: grand-avignon.osm2pgsql-shapefiles [SHAPE]
grand-avignon.osm-polygon (reader SHAPE_1)
    attributes: osm_id number(19,0), access char(10), aerialway char(32), aeroway char(9), amenity char(16), area char(3), barrier char(14), bicycle char(32), brand char(13), bridge char(32), boundary char(15), building char(23), covered char(3), culvert char(32), cutting char(32), disused char(3), embankment char(32), foot char(32), harbour char(32), highway char(13), historic char(19), horse char(32), junction char(32), landuse char(23), layer char(1), leisure char(17), lock char(32), man_made char(17), military char(32), motorcar char(32),
      name char(65), natural char(23), oneway char(32), operator char(35), population char(5), power char(11), place char(32), railway char(8), ref char(18), religion char(9), route char(32), service char(32), shop char(19), sport char(13), surface char(15), toll char(32), tourism char(12), tower:type char(7), tracktype char(32), tunnel char(3), water char(9), waterway char(9), wetland char(5), width char(32), wood char(10), z_order number(11,0), way_area number(32,10)
    -> public.planet_osm_polygon (writer POSTGIS_1)
Note: public.planet_osm_polygon: osm [POSTGIS]
public.planet_osm_polygon (writer POSTGIS_1)
    attributes: osm_id float8, access varchar(10), aerialway varchar(32), aeroway varchar(9), amenity varchar(16),BTREE, area varchar(3), barrier varchar(14),BTREE, bicycle varchar(32), brand varchar(13), bridge varchar(32), boundary varchar(15), building varchar(23),BTREE, covered varchar(3), culvert varchar(32), cutting varchar(32), disused varchar(3), embankment varchar(32), foot varchar(32), harbour varchar(32), highway varchar(13),BTREE, historic varchar(19),BTREE, horse varchar(32), junction varchar(32), landuse varchar(23),BTREE, layer varchar(1), leisure varchar(17),BTREE, lock varchar(32), man_made varchar(17), military varchar(32), motorcar varchar(32),
      name varchar(65), natural varchar(23),BTREE, oneway varchar(32), operator varchar(35), population varchar(5), power varchar(11), place varchar(32), railway varchar(8),BTREE, ref varchar(18), religion varchar(9), route varchar(32), service varchar(32), shop varchar(19), sport varchar(13), surface varchar(15), toll varchar(32), tourism varchar(12), tower:type varchar(7), tracktype varchar(32), tunnel varchar(3), water varchar(9), waterway varchar(9),BTREE, wetland varchar(5), width varchar(32), wood varchar(10), z_order float8, way_area float8
Note: grand-avignon.osm-point: grand-avignon.osm2pgsql-shapefiles [SHAPE]
grand-avignon.osm-point (reader SHAPE_1)
    attributes: osm_id number(19,0), access char(10), aerialway char(32), aeroway char(7), amenity char(18), area char(32), barrier char(14), bicycle char(3), brand char(13), bridge char(32), boundary char(32), building char(11), capital char(1), covered char(3), culvert char(32), cutting char(32), disused char(32), ele char(6), embankment char(32), foot char(3), harbour char(3), highway char(17), historic char(19), horse char(3), junction char(10), landuse char(24), layer char(1), leisure char(17), lock char(32), man_made char(17),
      military char(32), motorcar char(3), name char(74), natural char(9), oneway char(32), operator char(28), poi char(32), population char(5), power char(11), place char(17), railway char(14), ref char(20), religion char(9), route char(32), service char(32), shop char(21), sport char(12), surface char(5), toll char(32), tourism char(21), tower:type char(13), tunnel char(32), water char(32), waterway char(9), wetland char(32), width char(32), wood char(32), z_order number(11,0)
    -> public.planet_osm_point (writer POSTGIS_1)
Note: public.planet_osm_point: osm [POSTGIS]
public.planet_osm_point (writer POSTGIS_1)
    attributes: osm_id float8, access varchar(10), aerialway varchar(32), aeroway varchar(7), amenity varchar(18), area varchar(32), barrier varchar(14), bicycle varchar(3), brand varchar(13), bridge varchar(32), boundary varchar(32), building varchar(11), capital varchar(1), covered varchar(3), culvert varchar(32), cutting varchar(32), disused varchar(32), ele varchar(6), embankment varchar(32), foot varchar(3), harbour varchar(3), highway varchar(17), historic varchar(19), horse varchar(3), junction varchar(10), landuse varchar(24), layer varchar(1), leisure varchar(17), lock varchar(32), man_made varchar(17),
      military varchar(32), motorcar varchar(3), name varchar(74), natural varchar(9), oneway varchar(32), operator varchar(28), poi varchar(32), population varchar(5), power varchar(11), place varchar(17), railway varchar(14), ref varchar(20), religion varchar(9), route varchar(32), service varchar(32), shop varchar(21), sport varchar(12), surface varchar(5), toll varchar(32), tourism varchar(21), tower:type varchar(13), tunnel varchar(32), water varchar(32), waterway varchar(9), wetland varchar(32), width varchar(32), wood varchar(32), z_order float8
Note: grand-avignon.osm-line: grand-avignon.osm2pgsql-shapefiles [SHAPE]
grand-avignon.osm-line (reader SHAPE_1)
    attributes: osm_id number(19,0), access char(12), aerialway char(32), aeroway char(7), amenity char(16), area char(2), barrier char(14), bicycle char(10), brand char(32), bridge char(10), boundary char(15), building char(3), covered char(3), culvert char(32), cutting char(3), disused char(3), embankment char(3), foot char(10), harbour char(32), highway char(24), historic char(3), horse char(7), junction char(10), landuse char(23), layer char(2), leisure char(14), lock char(3), man_made char(10), military char(32), motorcar char(10),
      name char(68), natural char(23), oneway char(3), operator char(35), population char(7), power char(10), place char(32), railway char(9), ref char(28), religion char(9), route char(7), service char(16), shop char(32), sport char(13), surface char(13), toll char(3), tourism char(32), tower:type char(32), tracktype char(6), tunnel char(16), water char(32), waterway char(9), wetland char(32), width char(4), wood char(10), z_order number(11,0), way_area number(32,10)
    -> public.planet_osm_line (writer POSTGIS_1)
Note: public.planet_osm_line: osm [POSTGIS]
public.planet_osm_line (writer POSTGIS_1)
    attributes: osm_id float8, access varchar(12), aerialway varchar(32), aeroway varchar(7),BTREE, amenity varchar(16), area varchar(2), barrier varchar(14), bicycle varchar(10), brand varchar(32), bridge varchar(10), boundary varchar(15), building varchar(3), covered varchar(3), culvert varchar(32), cutting varchar(3), disused varchar(3), embankment varchar(3), foot varchar(10), harbour varchar(32), highway varchar(24),BTREE, historic varchar(3), horse varchar(7), junction varchar(10), landuse varchar(23), layer varchar(2), leisure varchar(14), lock varchar(3), man_made varchar(10), military varchar(32), motorcar varchar(10),
      name varchar(68), natural varchar(23), oneway varchar(3), operator varchar(35), population varchar(7), power varchar(10), place varchar(32), railway varchar(9),BTREE, ref varchar(28), religion varchar(9), route varchar(7), service varchar(16), shop varchar(32), sport varchar(13), surface varchar(13), toll varchar(3), tourism varchar(32), tower:type varchar(32), tracktype varchar(6), tunnel varchar(16), water varchar(32), waterway varchar(9), wetland varchar(32), width varchar(4), wood varchar(10), z_order float8, way_area float8
